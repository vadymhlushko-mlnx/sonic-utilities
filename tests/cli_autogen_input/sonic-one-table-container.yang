module sonic-one-table-container {

    yang-version 1.1;

	namespace "http://github.com/Azure/sonic-one-table";
	prefix one-table;

	container sonic-one-table-container {

		container FIRST_TABLE {

			description "FIRST_TABLE description";
		}
	}
}
