module sonic-grouping{

    yang-version 1.1;

	namespace "http://github.com/Azure/s-grouping";
	prefix s-grouping;

	grouping target {
    	leaf t_address {
    		type inet:ip-address;
    		description "Target IP address.";
    	}
    	leaf t_port {
    		type inet:port-number;
    		description "Target port number.";
    	}
    }
}
