module sonic-test-1 {

    yang-version 1.1;

	namespace "http://github.com/Azure/sonic-test-1";
	prefix many-test-1;

	container sonic-test-1 {
		/* sonic-test-1 - top level container, it have:
		 * 2 table containers. Table container - represent Config DB table name.
		 */

		container TABLE_1 {
			/* TABLE_1 - table container, it have:
			 * 2 object containers, Object container - represent Confg DB object name.
			 */
			description "TABLE_1 description";

			container OBJECT_1 {
				/* OBJECT_1 - object container, it have:
				 * 1 leaf,
				 * 1 leaf-list
				 * 1 choice
				 */
				description "OBJECT_1 description";

				leaf OBJ_1_LEAF_1 {
					description "OBJ_1_LEAF_1 description";
					type string;
				}

				leaf-list OBJ_1_LEAF_LIST_1 {
					mandatory true;
					type string;
				}

				choice OBJ_1_CH_1 {
					case OBJ_1_CH_1_CASE_1 {
						leaf OBJ_1_CH_1_LEAF_1 {
							type uint16;
						}
					}
					case OBJ_1_CH_1_CASE_2 {
						leaf OBJ_1_CH_1_LEAF_2 {
							type string;
						}
					}
				}
			}

			container OBJECT_2 {
				/* OBJECT_2 - table container, it have:
				 * 2 leaf,
				 * 2 leaf-list
				 * 2 choice
				 */
				description "OBJECT_2 description";

				leaf OBJ_2_LEAF_1 {
					description "OBJ_2_LEAF_1 description";
					type string;
				}

				leaf OBJ_2_LEAF_2 {
					mandatory true;
					type string;
				}

				leaf-list OBJ_2_LEAF_LIST_1 {
					description "OBJ_2_LEAF_LIST_1 description";
					mandatory true;
					type string;
				}

				leaf-list OBJ_2_LEAF_LIST_2 {
					type string;
				}

				choice OBJ_2_CH_1 {
					case OBJ_2_CH_1_CASE_1 {
						leaf OBJ_2_CH_1_LEAF_1 {
							type uint16;
						}
					}
					case OBJ_2_CH_1_CASE_2 {
						leaf OBJ_2_CH_1_LEAF_2 {
							type string {
								type string;
							}
						}
					}
				}

				choice OBJ_2_CH_2 {
					case OBJ_2_CH_2_CASE_1 {
						leaf OBJ_2_CH_2_LEAF_1 {
							type uint16;
						}
					}
					case OBJ_2_CH_2_CASE_2 {
						leaf OBJ_2_CH_2_LEAF_2 {
							type string {
								type string;
							}
						}
					}
				}
			}
		}

		container TABLE_2 {

		}
	}
}
