module sonic-2-table-containers {

    yang-version 1.1;

	namespace "http://github.com/Azure/s-2-table";
	prefix s-2-table;

	container sonic-2-table-containers {

		container TABLE_1 {

			description "TABLE_1 description";
		}

		container TABLE_2 {

			description "TABLE_2 description";
		}
	}
}
