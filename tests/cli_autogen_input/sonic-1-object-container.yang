module sonic-1-object-container {

    yang-version 1.1;

	namespace "http://github.com/Azure/s-1-object";
	prefix s-1-object;

	container sonic-1-object-container {

		container TABLE_1 {

			description "TABLE_1 description";

			container OBJECT_1 {

				description "OBJECT_1 description";
			}
		}
	}
}
